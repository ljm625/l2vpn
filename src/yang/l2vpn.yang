module l2vpn {

  namespace "http://example.com/l2vpn";
  prefix l2vpn;

  import ietf-inet-types {
    prefix inet;
  }
  import tailf-common {
    prefix tailf;
  }
  import tailf-ncs {
    prefix ncs;
  }

  description
    "Bla bla...";

  revision 2016-01-01 {
    description
      "Initial revision.";
  }

  list l2vpn {
    description "This is an RFS skeleton service";
    key name;
    leaf name {
      tailf:info "Unique service id";
      tailf:cli-allow-range;
      type string;
    }

    uses ncs:service-data;
    ncs:servicepoint l2vpn-servicepoint;

    container endpoint1 {
      leaf device {
        type leafref{
          path "/ncs:devices/ncs:device/ncs:name";
        }
      }
      container interface {
        leaf GigabitEthernet {
            type string;
        }
      }
      leaf loopback-ip {
        type inet:ipv4-address;
      }
    }


    container endpoint2 {
      leaf device {
        type leafref{
          path "/ncs:devices/ncs:device/ncs:name";
        }
      }
      container interface {
        leaf GigabitEthernet {
            type string;
        }
      }
      leaf loopback_ip {
        type inet:ipv4-address;
      }
    }
    
    leaf pw-id {
        type uint8;
    }
  }
}
